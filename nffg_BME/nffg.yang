module nffg {
    namespace "http://csikor.tmit.bme.hu/netconf/unify/nffg";
    prefix "nffg";
    organization "BME-TMIT";
    contact "Levente Csikor <csikor@tmit.bme.hu>,
             Balazs Sonkoly <sonkoly@tmit.bme.hu>";
    
    revision 2015-10-23 
    {
        description "Network Function Forwarding Graph (NF-FG) data model";
    }
    
    //======================== REUSABLE GROUPS ================================
    
    // ------------ LINK IS DESCRIBED BY ITS ENDPOINTS AND PORTS -------
    grouping link {
        leaf id {
            type string;
            mandatory true;
        }

        leaf src_node {
            type string;
            mandatory true;
        }
	
        leaf src_port {
            type string;
            mandatory true;
        }
	
        leaf dst_node {
            type string;
            mandatory true;
        }
	
        leaf dst_port {
            type string;
            mandatory true;
        }
    }
    
    // ---------- NODE AND LINK RESOURCES -------------------
    grouping node_resource {
    	leaf cpu {
            type string;
            mandatory true;
        }
        
        leaf mem {
            type string;
            mandatory true;
        }
        
        leaf storage {
            type string;
            mandatory true;
        }

        leaf delay {
            type string;
            mandatory true;
        }

        leaf bandwidth {
            type string;
            mandatory true;
        }
    }
    
    grouping link_resource {
    	
    	leaf delay {
            type string;
            mandatory false;
        }
        
        leaf bandwidth {
            type string;
            mandatory false;
        }
    }
    
    //#####################################################################
    
    // --------========== MAIN CONTAINER STARTS HERE =========-------------
    container nffg {
        
        description "Container for a single NF-FG";
        container parameters {
            //mandatory true;
            leaf id {
                type string;
                mandatory true;
            }
            leaf name {
                type string;
                mandatory false;
            }
            leaf version {
                type string;
                mandatory true;
            }
        }

        // ------------------------ NF NODES -------------------------
        list node_nfs {
            description "Network Function (NF) nodes in the graph";
            min-elements 0;
            key "id";
      
            leaf id {
                type string;
                mandatory true;
            }
      
            leaf name {
                type string;
                mandatory false;
            }
      
            leaf functional_type {
                type string;
                mandatory true;
            }
      
            container specification {
                //mandatory false;
	
                leaf deployment_type {
                    type string;
                    mandatory false;
                }
	
                container resources {
                    //mandatory false;          
                    uses node_resource;
                }
            }
      
            list ports {
                min-elements 1;
                key "id";
                
                leaf id {
                    type string;
                    mandatory true;
                }
	
                leaf-list property {
                    min-elements 1;
                    type string;
                    description "formerly known as type";
                }
            }
        }
    
        // ------------------------ SAP NODES -------------------------
        list node_saps {
            description "SAP nodes in the graph";
            min-elements 1;
            key "id";
      
            leaf id {
                type string;
                mandatory true;
            }
      
            leaf name {
                type string;
                mandatory false;
            }

            leaf domain {
                type string;
                mandatory false;
            }
      
            list ports {
                min-elements 1;
                key "id";
	
                leaf id {
                    type string;
                    mandatory true;
                }
	
                leaf-list property {
                    min-elements 1;
                    type string;
                    description "formerly known as type";
                }
            }
        }
    
        // ----------------- INFRASTRUCTURE NODES -----------------------
        list node_infras {
            description "Infrastructure nodes";
            min-elements 0;
            key "id";
      
            leaf id {
                type string;
                mandatory true;
            }
      
            leaf name {
                type string;
                mandatory false;
            }

            leaf domain {
                type string;
                mandatory false;
            }
      
            leaf type {
                type string;
                mandatory true;
            }

            list supported {
                min-elements 0;
                key "functional_type";

                leaf functional_type {
                    type string;
                    mandatory true;
                }
            }
      
            container resources {
                //mandatory false;
                uses node_resource;
            }
			
            list ports {
                min-elements 1;
                key "id";

                leaf id {
                    type string;
                    mandatory true;
                }
				
                leaf-list property {
                    min-elements 1;
                    type string;
                    description "formerly known as type";
                }

                list flowrules {
                    min-elements 0;
                    key "id";
                    
                    leaf id {
                        type string;
                        mandatory true;
                    }
                    
                    leaf match {
                        type string;
                        mandatory true;
                    }
                    
                    leaf action {
                        type string;
                        mandatory true;
                    }

                    leaf bandwidth {
                        type string;
                        mandatory false;
                    }
                }
            }
        }
		
        // -------------------- INFRASTRUCTURE LINKS ------------------
        list edge_links {
            description "Static and dynamic links";
            min-elements 0;
            key "id";
			
            uses link;
            
            leaf backward {
                type string;
                mandatory false;
            }
            
            container reqs {
                //mandatory false;
                uses link_resource;
            }
        }

        // --------------- SG NEXT_HOPS, LINKS IN SG -----------------
        list edge_sg_nexthops {
            description "Edges between SG elements";
            min-elements 0;
            key "id";
			
            uses link;
			
            leaf flowclass {
                type string;
                mandatory false;
            }
        }
		
        //---------------- SG REQUIREMENTS ---------------------
        list edge_reqs {
            description "Requirements between SG elements";
            min-elements 0;
            key "id";
			
            uses link;
			
            container reqs {
                //mandatory true;
                uses link_resource;
            }

            list sg_path {
                min-elements 1;
                key "edge_sg_nexthop_id";
                
                leaf edge_sg_nexthop_id {
                    type string;
                    mandatory true;
                }
            }
        }
    }
}
