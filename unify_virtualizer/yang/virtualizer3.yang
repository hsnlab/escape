module virtualizer3 {
  namespace "urn:unify:virtualizer";
  prefix "virtualizer";
  organization "ETH";
  contact "Robert Szabo <robert.szabo@ericsson.com>";

  revision 2015-07-20 
  {
    description "Virtualizer's revised (simplified) data model";
  }

  //======================== REUSABLE GROUPS ================================

  grouping id-name {
    leaf id { type string; }
    leaf name { type string;}
  }

  grouping id-name-type {
    uses id-name;
    leaf type {
      type string;
      // for infrastructue view: mandatory true; --> refined in infrastrucutre view
      mandatory false;
    }
  }

  // ------------ PORTS -------
  
  typedef port-ref {
    type string;
  }
  
  // grouping port-sap-vxlan {
  //   leaf vxlan {type string;} // for example
  //   // container vx_lan {
  //   //   leaf remote_ip { type string; }
  //   //   leaf local_ip { type string; }
  //   //   leaf tunnel_key { type uint32; }
  //   // }
  // }
  
  // grouping port-type {
  //   leaf port_type {type string;} // TODO: enumerated
  //   choice port-type {
  //     description "Different port types: abstract and SAPs";
  //     case port-abstract {
  //       leaf capability { type string; }
  //     }
  //     case port-sap {
  //       leaf sap_type {type string;} // TODO: enumerated
  //       choice sap-type {
  //         case vx-lan { // for example
  //           uses port-sap-vxlan;
  //         }
  //       }
  //     }
  //   }
  // }

  grouping port {
    uses id-name;
    // uses port-type;
    leaf port_type {type string;}
    leaf capability { type string;}
    leaf sap {type string;}
  }

  // ------------ FLOW CONTROLS -------
  grouping link-resource {
    leaf delay {
      type string;
      mandatory false;
    }
    leaf bandwidth {
      type string;
      mandatory false;
    }
  }

  grouping flowentry {
    uses id-name;
    leaf priority {
      type string;
      }
    leaf port {
      type leafref {
        path "";
      }
      mandatory true;
    }
    leaf match {
      type string;
      mandatory true;
    }
    leaf action {
      type string;
      mandatory true;
    }
    leaf out {
      type leafref {
        path "";
      }
    }
    container resources{
      uses link-resource;
    }

  }

  grouping flowtable {
    container flowtable {
      list flowentry {
        key "id";
        uses flowentry;
      }
    }
  }
    
  // ------------ LINKS  -------


  grouping link {
    uses id-name;
    leaf src {
      type leafref {
        path "";
      }
    }
    leaf dst {
      type leafref {
        path "";
      }
    }
    container resources{
      uses link-resource;
    }
  }

  grouping links {
    container links {
      list link {
        key "src dst";
        uses link;
      }
    }
  }

  // ---------- NODE -------------------

  grouping software-resource {
    leaf cpu {
      type string;
      mandatory true;
    }
    leaf mem {
      type string;
      mandatory true;
    }
    leaf storage {
      type string;
      mandatory true;
    }
  }

  grouping node {
    description "Any node: infrastructure or NFs";
    uses id-name-type;
    container ports {
      list port{
        key "id";
        uses port;
      }
    }
    uses links;
    container resources{
      uses software-resource;
    }
  }

  grouping nodes {
    list node{
      key "id";
      uses node;
    }
  }
  
  grouping infra-node { // they can contain other nodes (as NFs)
    uses node {
        refine type {
            mandatory true;
        }
    }
    container NF_instances {
      uses nodes;
    }
    container capabilities {
      container supported_NFs { // if supported NFs are enumerated
        uses nodes;
      }
    }
    uses flowtable;
  }
  


  //======================== NF-FG: Virtualizer and the Mapped request ================================

  container virtualizer {
    description "Container for a single virtualizer";
    uses id-name;

    container nodes{
      list node{ // infra nodes
        key "id";
        uses infra-node;
      }
    }
    uses links; // infra links
  }
}
